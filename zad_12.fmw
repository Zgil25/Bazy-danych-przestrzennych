FME workspace zad_12.fmw

Parameters:
- SourceDataset_SHAPEFILE = ""$(FME_MF_DIR)pliki\T2019_KAR_POI_TABLE.shp" "$(FME_MF_DIR)pliki\T2019_KAR_STREET_NODE.shp" "$(FME_MF_DIR)pliki\T2019_KAR_STREETS.shp""   # Source Esri Shapefile(s)
- SourceDataset_CSV2 = $(FME_MF_DIR)wspolrzedne.csv   # Source CSV (Comma Separated Value) File(s)
- DestDataset_GEOJSON = $(FME_MF_DIR)geojs\punkty_bufor.json   # Destination GeoJSON File
- DestDataset_FILEGDB = $(FME_MF_DIR)geobaza.gdb   # File Geodatabase

Readers:
- SHAPEFILE_1: SHAPEFILE from $(SourceDataset_SHAPEFILE)
- CSV2_1: CSV2 from $(SourceDataset_CSV2)

Writers:
- GEOJSON_1: GEOJSON to $(DestDataset_GEOJSON)
- FILEGDB_1: FILEGDB to $(DestDataset_FILEGDB)

CSV (reader CSV2_1)
    attributes: x real32, y real32
    -> LineBuilder
LineBuilder
    ACCUM_INPUT_ATTRS_LOOKUP = One
    REMOVE_DUPLICATES_LOOKUP = NO
    ACCUM_INPUT_ATTRS = Use Attributes From One Feature
    REMOVE_DUPLICATES = No
    LINE -> Reprojector
Reprojector
    DEST = DHDN.Berlin/Cassini
    INTERPOLATION_TYPE = NearestNeighbor
    RASTER_CELL_SIZE = PreserveCells
    RASTER_TOLERANCE = 0.0
    REPROJECTED -> NajkrotszaTrasaA [FROM-TO]
    REPROJECTED -> NajkrotszaTrasaB [FROM-TO]
T2019_KAR_STREETS (reader SHAPEFILE_1)
    attributes: LINK_ID long, ST_NAME varchar(254), REF_IN_ID long, NREF_IN_ID long, FUNC_CLASS varchar(1), SPEED_CAT varchar(1), FR_SPEED_L long, TO_SPEED_L long, DIR_TRAVEL varchar(1)
    -> Reprojector_4
Reprojector_4
    DEST = DHDN.Berlin/Cassini
    INTERPOLATION_TYPE = NearestNeighbor
    RASTER_CELL_SIZE = PreserveCells
    RASTER_TOLERANCE = 0.0
    REPROJECTED -> NajkrotszaTrasaA [NETWORK]
    REPROJECTED -> Tester
NajkrotszaTrasaA: ShortestPathFinder
    ALLOW_UTURNS = Yes
    REORDER_MODE = NONE
    SNAP_POINTS = Yes
    SNAP_TOLERANCE = 20
    THREE_D = No
    WEIGHT_ATTR_CHOICE = BY_LENGTH
    PATH -> Bufferer
    PATH -> Wariant_A
Wariant_A: AttributeCreator
    ATTR_TABLE = SET_TO wariant (varchar(13)) = bez_kosztow_A
    INPUT_PORT_CONNECTED = CONNECTED
    -> LengthCalculator
LengthCalculator
    DIM = 2
    LEN_ATTR = _length
    MULT = 1
    -> Skrzyżowania_A [Filter]
Tester
    BOOL_OP = OR
    TEST_CLAUSE = TEST @Value(DIR_TRAVEL) != B
    TEST_MODE = TEST
    PASSED -> Jednokierunkowe
    FAILED -> Dwukierunkowe
Jednokierunkowe: AttributeCreator
    ATTR_TABLE:
      SET_TO ForwardCost (uint32) = FME_CONDITIONAL:DEFAULT_VALUE'1'BOOL_OP;OR;COMPOSITE_TEST;1;TEST @Value(DIR_TRAVEL) = T'99999'FME_NUM_CONDITIONS2___
      SET_TO ReverseCost (uint32) = FME_CONDITIONAL:DEFAULT_VALUE'1'BOOL_OP;OR;COMPOSITE_TEST;1;TEST @Value(DIR_TRAVEL) = F'99999'FME_NUM_CONDITIONS2___
    INPUT_PORT_CONNECTED = CONNECTED
    -> NajkrotszaTrasaB [NETWORK]
Dwukierunkowe: AttributeCreator
    ATTR_TABLE:
      SET_TO ForwardCost (uint8) = 1
      SET_TO ReverseCost (uint8) = 1
    INPUT_PORT_CONNECTED = CONNECTED
    -> NajkrotszaTrasaB [NETWORK]
NajkrotszaTrasaB: ShortestPathFinder
    ALLOW_UTURNS = Yes
    REORDER_MODE = NONE
    SNAP_POINTS = Yes
    SNAP_TOLERANCE = 20
    THREE_D = No
    WEIGHT_ATTR_1 = @Value(ForwardCost)
    WEIGHT_ATTR_2 = @Value(ReverseCost)
    WEIGHT_ATTR_CHOICE = BY_TWO_ATTRIBUTES
    PATH -> Bufferer
    PATH -> Wariant_B
Bufferer
    ANGLE = 22.5
    CAP_STYLE_LOOKUP = CAP_ARC
    CORNER_STYLE_LOOKUP = JOIN_ARC
    MODE = AREA
    OFFSET = 5
    OFFSET_UNITS = METERS
    PRECISION = APPROX
    CAP_STYLE = Arc
    CORNER_STYLE = Arc
    BUFFERED -> SpatialFilter [Filter]
Wariant_B: AttributeCreator
    ATTR_TABLE = SET_TO wariant (varchar(13)) = z_kosztami_B
    INPUT_PORT_CONNECTED = CONNECTED
    -> LengthCalculator_2
LengthCalculator_2
    DIM = 2
    LEN_ATTR = _length
    MULT = 1
    -> Skrzyżowania_B [Filter]
T2019_KAR_STREET_NODE (reader SHAPEFILE_1)
    attributes: NODE_ID long, LINK_ID long, POINT_NUM long, Z_LEVEL long, INTERSECT varchar(1), LAT number(31,15), LON number(31,15)
    -> Reprojector_3
Reprojector_3
    DEST = DHDN.Berlin/Cassini
    INTERPOLATION_TYPE = NearestNeighbor
    RASTER_CELL_SIZE = PreserveCells
    RASTER_TOLERANCE = 0.0
    REPROJECTED -> Skrzyżowania_A [Candidate]
    REPROJECTED -> Skrzyżowania_B [Candidate]
Skrzyżowania_A: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator
Skrzyżowania_B: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator
StatisticsCalculator
    ATTR_ACCUM_MODE = None
    CALCULATION_MODE = NUMERIC
    FEAT_STATS = _length,NUMERIC_MODE,,,COUNT,,MEAN,,,,,,,,
    GROUP_BY = wariant
    SUMMARY -> AttributeRenamer
AttributeRenamer
    ATTR_TABLE:
      RENAME_SET_DEFAULT wariant
      RENAME_SET_DEFAULT _length.mean > dlugosc_trasy
      RENAME_SET_DEFAULT _length.total_count > liczba_skrzyzowan
    KEEP_RENAMED_ONLY = no
    MISSING_INPUT_ATTRS = REMOVE
    -> Statystyki (writer FILEGDB_1)
Statystyki (writer FILEGDB_1)
    attributes: wariant text(13), dlugosc_trasy double, liczba_skrzyzowan text(20)
T2019_KAR_POI_TABLE (reader SHAPEFILE_1)
    attributes: POI_ID long, LINK_ID long, TYPE varchar(250), POI_NAME varchar(250), ST_NAME varchar(250), LAT number(31,15), LON number(31,15)
    -> Reprojector_2
Reprojector_2
    DEST = DHDN.Berlin/Cassini
    INTERPOLATION_TYPE = NearestNeighbor
    RASTER_CELL_SIZE = PreserveCells
    RASTER_TOLERANCE = 0.0
    REPROJECTED -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> POI_w_buforze (writer GEOJSON_1)
POI_w_buforze (writer GEOJSON_1)
    attributes: x float, y float, _total_cost string, POI_ID int, LINK_ID int, TYPE string, POI_NAME string, ST_NAME string, LAT string, LON string, _predicate string
